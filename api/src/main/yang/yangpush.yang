module yangpush {
    yang-version 1;
    namespace "urn:opendaylight:params:xml:ns:yang:yangpush";
    prefix "yangpush";

    import notifications { prefix n; revision-date "2008-07-14"; }

    contact
        "ambtripa@cisco.com";
    
    description
        "implements data-push subscription ontop
         od NETCONF notification RFC.";
    
    reference
        "RFC 5277.";

    revision "2015-01-05" {
        description "Initial revision of yangpush model";
    }
    
	rpc cs {
        description
            "This is atest RPC to initiate create-subscription
            for ds-push stream to the given node name if available. ";
        input {
            leaf node-name {
                mandatory true;
                type string;
                description
                    "Name of the mounted node to be displayed";
            }
            leaf stream {
                type string;
                description
                    "stream name";
            }
            leaf period {
                type uint32;
                description
                    "period for a periodic subscription";
            }
            leaf subscription-id {
                type string;
                description 
                    "unique subscription id";
            }
            anyxml filter {
                description
                    "subtree filter string";
            }
        }
    }    
}
