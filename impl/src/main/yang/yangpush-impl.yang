module yangpush-impl {
    yang-version 1;
    namespace "urn:opendaylight:params:xml:ns:yang:yangpush:impl";
    prefix "yangpush-impl";

    import config { prefix config; revision-date 2013-04-05; }
    //import opendaylight-md-sal-binding { prefix md-sal-binding; revision-date 2013-10-28;}
    import opendaylight-md-sal-dom {prefix dom;}

    description
        "Service definition for yangpush project";

    revision "2014-12-10" {
        description
            "Initial revision";
    }

    identity yangpush {
        base config:module-type;
        config:java-name-prefix Yangpush;
    }

    augment "/config:modules/config:module/config:configuration" {
        case yangpush {
            when "/config:modules/config:module/config:type = 'yangpush'";
            /*container broker {
                uses config:service-ref {
                    refine type {
                        mandatory true;
                        config:required-identity md-sal-binding:binding-broker-osgi-registry;
                    }
                }
            }*/
            // BI broker
            container dom-broker {
                uses config:service-ref {
                    refine type {
                        mandatory true;
                        config:required-identity dom:dom-broker-osgi-registry;
                    }
                }
            }
        }
    }
}
